Attribute VB_Name = "MainForms"
Attribute VB_Base = "0{60E989B0-24A1-45B6-BF9A-CF3C8B84A791}{D78A0A7C-A7B4-4836-9C16-6EE36E5B9639}"
Attribute VB_GlobalNameSpace = False
Attribute VB_Creatable = False
Attribute VB_PredeclaredId = True
Attribute VB_Exposed = False
Attribute VB_TemplateDerived = False
Attribute VB_Customizable = False

Private Sub CommandButton1_Click()

Dim CATIA As Object
Set CATIA = GetObject(, "CATIA.Application")

Dim MyDrawingDoc As DrawingDocument
Set MyDrawingDoc = CATIA.ActiveDocument

Dim MyDrawingSheets As DrawingSheets
Set MyDrawingSheets = MyDrawingDoc.Sheets

Dim MyDrawingSheet As DrawingSheet
Set MyDrawingSheet = MyDrawingSheets.ActiveSheet

Dim MyDrawingViews As DrawingViews
Set MyDrawingViews = MyDrawingSheet.Views

Dim drwviews As DrawingViews  'make background view active
Set drwviews = MyDrawingSheet.Views
drwviews.Item(2).Activate
'drwviews.Item("Background View").Activate

'Set myText.... As DrawingText - adding texts
Set myText = MyDrawingViews.ActiveView.Texts.Add("Dibujado", 22, 38)  'coordinates x=22, y=38 of left bottom corner of the text location
Set myText1 = MyDrawingViews.ActiveView.Texts.Add("Corregido", 22, 31)
Set myText2 = MyDrawingViews.ActiveView.Texts.Add("Fecha", 57, 46)
Set myText3 = MyDrawingViews.ActiveView.Texts.Add("DD-mm-08", 57, 38)
Set myText4 = MyDrawingViews.ActiveView.Texts.Add("DD-mm-08", 57, 31)
Set myText5 = MyDrawingViews.ActiveView.Texts.Add("Nombre", 87, 46)
Set myText6 = MyDrawingViews.ActiveView.Texts.Add("Jefatura", 87, 38)
Set myText7 = MyDrawingViews.ActiveView.Texts.Add("Delineante", 87, 31)
Set myText8 = MyDrawingViews.ActiveView.Texts.Add("Empresa S.A.", 159, 40)
Set myText9 = MyDrawingViews.ActiveView.Texts.Add("C/laredo 8, 2B", 159, 32)

Set myText13 = MyDrawingViews.ActiveView.Texts.Add("Escalas:", 22, 23)
Set myText14 = MyDrawingViews.ActiveView.Texts.Add("1/X", 22, 17)
Set myText15 = MyDrawingViews.ActiveView.Texts.Add("1/X", 22, 11)
Set myText16 = MyDrawingViews.ActiveView.Texts.Add("Firma", 128, 38)

Dim iFortSize1 As Double 'font text size
iFontSize1 = 3.5
myText1.SetFontSize 0, 0, 3.5    'iFontSize

'next lines with a different size for fonts - 2.5
Set myText10 = MyDrawingViews.ActiveView.Texts.Add("Sustituye a: xxx-08", 155, 22)
Set myText11 = MyDrawingViews.ActiveView.Texts.Add("Sustituido por: xxx-08", 155, 12)

Dim iFortSize10 As Double
iFontSize10 = 2.5
myText10.SetFontSize 0, 0, 2.5    'iFontSize

Dim iFortSize11 As Double
iFontSize11 = 2.5
myText11.SetFontSize 0, 0, 2.5    'iFontSize

'next lines with a different size for fonts - 5
Set myText12 = MyDrawingViews.ActiveView.Texts.Add("plano No xxx-08", 70, 18)

Dim iFortSize12 As Double
iFontSize12 = 5#
myText12.SetFontSize 0, 0, 5#    'iFontSize

'Declarations

Dim DrwDocument   As DrawingDocument
Dim DrwSheets     As DrawingSheets
Dim DrwSheet      As DrawingSheet
Dim DrwView       As DrawingView
Dim DrwTexts      As DrawingTexts
Dim Text          As DrawingText
Dim Fact          As Factory2D
Dim Point         As Point2D
Dim Line          As Line2D
Dim Cicle         As Circle2D
Dim Selection     As Selection
Dim GeomElems     As GeometricElements


  Set DrwDocument = CATIA.ActiveDocument
  Set DrwSheets = DrwDocument.Sheets
  Set Selection = DrwDocument.Selection
  Set DrwSheet = DrwSheets.ActiveSheet
  Set DrwView = DrwSheet.Views.ActiveView
  Set DrwTexts = DrwView.Texts
  Set Fact = DrwView.Factory2D
  Set GeomElems = DrwView.GeometricElements


'draw frame bottom line
    Set Line1 = Fact.CreateLine(20, 5, 205, 5) 'these are the coordinates of the starting point x=20, y=5 of the line and end point of the line x=205, y=5
    Line1.Name = "Line1"
    CATIA.ActiveDocument.Selection.VisProperties.SetRealWidth 3, 1
    CATIA.ActiveDocument.Selection.Clear
   
'draw frame upper line
    Set Line2 = Fact.CreateLine(20, 292, 205, 292)
    Line2.Name = "Line2"
    CATIA.ActiveDocument.Selection.VisProperties.SetRealWidth 3, 1
    CATIA.ActiveDocument.Selection.Clear
 
'draw a thin line
    Set Line3 = Fact.CreateLine(20, 40, 120, 40)
    Line3.Name = "Line3"
    CATIA.ActiveDocument.Selection.Add Line3
    Set visProperties1 = CATIA.ActiveDocument.Selection.VisProperties
    visProperties1.SetRealLineType 1, 0.2
    Set visProperties1 = CATIA.ActiveDocument.Selection.VisProperties
    visProperties1.SetRealWidth 1, 0.2

   drwviews.Item(1).Activate
    CATIA.ActiveDocument.Selection.Clear
    End
    
' You can continue to draw the rest of the lines and try other settings...


End Sub

Private Sub CommandButton3_Click()

End Sub

Private Sub ComboBox2_Change()
ComboBox2.AddItem "0.8"
End Sub

Private Sub CommandButton4_Click()
  End
End Sub

Private Sub CommandButton6_Click()

End Sub

Private Sub Frame1_Click()

End Sub

Private Sub GenFTB_Click()

End Sub

Private Sub Label1_Click()

End Sub

Private Sub Label2_Click()

End Sub

Private Sub Label3_Click()

End Sub

Private Sub Label5_Click()

End Sub

Private Sub ListBox1_Click()
ListBox1.AddItem "a"
ListBox1.AddItem "b"
ListBox1.AddItem "c"
ListBox1.List = Array("a", "b", "c")

End Sub

Private Sub UserForm_Click()
 
End Sub

Attribute VB_Name = "图框模块"
Sub CATMain()

  MainForms.Show 0
   

End Sub
